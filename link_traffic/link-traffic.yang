module link-traffic {
   namespace "urn:ietf:xml:ns:yang:link-traffic";
   prefix link-traffic;
   organization "CEZNET, z.s.p.o.";
   contact "hlavaj20@fit.cvut.cz";
   description "Module checks running links and counts traffic on them.";
   revision "2017-08-17" {
      description "Initial revision.";
   }

   container links {
      description "Links configuration parameters.";
      list link {
         key "link_id";
         description "List of links on the collector.";
         min-elements 1;
         leaf link_id {
            type uint8 {
               range "0..100";
            }
            mandatory true;
            description "Link number, used for internal purposes.";
         }
         leaf name {
            type string{
               pattern "[-_a-zA-Z0-9]*";
               length "1..100";
            }
            mandatory true;
            description "Name of link.";
         }
         leaf color {
            type string{
               pattern "[0-9a-fA-F]{6}";
            }
            description "Color for munin graphs.";
         }
      }
   }
} //TODO enabled linx
